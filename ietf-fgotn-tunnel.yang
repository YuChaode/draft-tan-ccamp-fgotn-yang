module ietf-fgotn-tunnel {
   /* TODO: FIXME */
     yang-version 1.1;

   namespace "urn:ietf:params:xml:ns:yang:ietf-fgotn-tunnel";
   prefix "fgotn-tnl";

  import ietf-te {
    prefix "te";
    reference "RFC XXXX - A YANG Data Model for Traffic Engineering 
               Tunnels, Label Switched Paths and Interfaces";
  }
  
  import ietf-otn-tunnel {
    prefix "otn-tnl";
    reference  "RFC YYYY - OTN Tunnel YANG Model";
  }

  organization
    "Internet Engineering Task Force (IETF) CCAMP WG";
  contact
    "
      ID-draft editor:
        Yanxia Tan (tanyx11@chinaunicom.cn);
        Yanlei Zheng (zhengyanlei@chinaunicom.cn);
        YANG Zhao (zhaoyangyjy@chinamobile.com);
        Italo Busi (italo.busi@huawei.com);
        Chaode Yu (yuchaode@huawei.com);
    ";

  description
    "This module defines a YANG data model for fgOTN-specific 
     extension based on existing network topology models. The model 
     fully conforms to the Network Management Datastore Architecture
     (NMDA).

     Copyright (c) 2021 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see
     the RFC itself for full legal notices.";

  revision 2024-06-17 {
     description
       "initial version";
     reference
       "draft-tan-ccamp-fgotn-yang";
  }
  
  /**
  augment "/te:te/te:tunnels/te:tunnel/te:primary-paths" +
          "/te:primary-path/te:te-bandwidth/te:technology" + 
          "/otn-tnl:otn/otn-tnl:otn-bandwidth" {
    leaf fgoduflex-bandwidth {
      type string;
      description 
        "The bandwidth of this fgOTN tunnel";
    }
  }
  20240703讨论后建议删除
**/

 //20240703增加fgOTN隧道带宽
  augment "/te:te/te:tunnels/te:tunnel/"
        + "te:te-bandwidth/te:technology/otn-tnl:otn" {
    leaf fgoduflex-bandwidth {
      type string;
      description 
        "Augment TE bandwidth of the fgOTN tunnel";
    }
  }
  
  //20240703增加在primary-path中指定跨域端口上的fgts-numbers
  augment "/te:te/te:tunnels/te:tunnel/"
        + "te:primary-paths/te:primary-path/"
        + "te:explicit-route-objects/"
        + "te:route-object-include-exclude/te:type/te:label/"
        + "te:label-hop/te:te-label/te:technology/otn-tnl:otn" + 
          "/otn-tnl:otn-label" {
    leaf fgts-numbers {
      type uint16;
      description 
        "Augment fgOTN timeslot information of this label hop";
    }
  }
  
  augment "/te:te/te:tunnels/te:tunnel/te:primary-paths" + 
          "/te:primary-path/te:primary-reverse-path" + 
          "/te:explicit-route-objects" + 
          "/te:route-object-include-exclude/te:type/te:label" + 
          "/te:label-hop/te:te-label/te:technology/otn-tnl:otn" + 
          "/otn-tnl:otn-label" {
    leaf fgts-numbers {
      type uint16;
      description 
        "Augment fgOTN timeslot information of this label hop";
    }
  }

  augment "/te:te/te:tunnels/te:tunnel/te:secondary-paths" + 
          "/te:secondary-path/te:explicit-route-objects" + 
          "/te:route-object-include-exclude/te:type/te:label" + 
          "/te:label-hop/te:te-label/te:technology/otn-tnl:otn" + 
          "/otn-tnl:otn-label" {
    leaf fgts-numbers {
      type uint16;
      description 
        "fgOTN timeslot information of this label hop";
    }
  }  

  augment "/te:te/te:tunnels/te:tunnel/te:secondary-reverse-paths" + 
          "/te:secondary-reverse-path/te:explicit-route-objects" + 
          "/te:route-object-include-exclude/te:type/te:label" + 
          "/te:label-hop/te:te-label/te:technology/otn-tnl:otn" + 
          "/otn-tnl:otn-label" {
    leaf fgts-numbers {
      type uint16;
      description 
        "fgOTN timeslot information of this label hop";
    }
  }
  
  augment "/te:te/te:lsps/te:lsp/te:lsp-actual-route-information" +
          "/te:lsp-actual-route-information/te:type/te:label" +
          "/te:label-hop/te:te-label/te:technology/otn-tnl:otn" +
          "/otn-tnl:otn-label" {
    leaf fgts-numbers {
      type uint16;
      description 
        "fgOTN timeslot information of this label hop";
    }
  }
  
}
